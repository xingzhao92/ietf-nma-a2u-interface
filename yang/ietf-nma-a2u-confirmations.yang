module ietf-nma-a2u-confirmations {
  yang-version 1.1;
  namespace "urn:ietf:params:xml:ns:yang:ietf-nma-a2u-confirmations";
  prefix nma-a2u-confirm;

  import ietf-nma-a2u-common { prefix nma-a2u-common; }
  import ietf-nma-a2u-tasks { prefix nma-a2u-task; }
  import ietf-yang-types { prefix yang; }

  organization "IETF NMOP Working Group";
  contact
    "WG Web: https://datatracker.ietf.org/wg/nmop/
     WG List: nmop@ietf.org";
  description
    "YANG data model for NMA human-in-the-loop confirmations.

     Copyright (c) 2026 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     This version of this YANG module is part of RFC XXXX; see
     the RFC itself for full legal notices.";

  revision 2026-05-27 {
    description "Initial revision.";
    reference "RFC XXXX";
  }

  container confirmations {
    description "Container for all confirmations.";

    list confirmation {
      key "confirmation-id";
      description "A pending or resolved confirmation.";

      leaf confirmation-id {
        type string;
        description "Unique confirmation identifier.";
      }

      leaf task-id {
        type leafref {
          path "/nma-a2u-task:tasks/nma-a2u-task:task/nma-a2u-task:task-id";
        }
        mandatory true;
        description "Associated task.";
      }

      leaf type {
        type nma-a2u-common:confirmation-type;
        mandatory true;
        description "Type of confirmation.";
      }

      leaf priority {
        type uint8 {
          range "1..10";
        }
        default "5";
        description "Priority level.";
      }

      leaf timeout-seconds {
        type uint32;
        default "300";
        description "Timeout for user response in seconds.";
      }

      leaf context {
        type anydata;
        mandatory true;
        description "Contextual data for rendering the confirmation card.";
      }

      leaf-list allowed-actions {
        type enumeration {
          enum approve { description "Approve as-is."; }
          enum reject { description "Reject the operation."; }
          enum modify-and-approve { description "Modify parameters then approve."; }
          enum escalate-to-human { description "Escalate to human operator."; }
        }
        min-elements 1;
        description "Actions allowed for this confirmation.";
      }

      leaf status {
        type enumeration {
          enum pending { description "Awaiting resolution."; }
          enum approved { description "Approved."; }
          enum rejected { description "Rejected."; }
          enum modified { description "Modified and approved."; }
          enum expired { description "Timed out."; }
          enum escalated { description "Escalated to human."; }
        }
        default "pending";
        description "Current status.";
      }

      container resolution {
        description "Resolution details.";

        leaf action {
          type enumeration {
            enum approve;
            enum reject;
            enum modify-and-approve;
            enum escalate-to-human;
          }
          description "Chosen action.";
        }

        leaf modified-params {
          type anydata;
          description "Modified parameters if action is modify-and-approve.";
        }

        leaf resolved-by {
          type string;
          description "Who resolved this confirmation.";
        }

        leaf resolved-at {
          type yang:date-and-time;
          description "Resolution timestamp.";
        }
      }
    }
  }
}
