module ietf-nma-a2u-intent {
  yang-version 1.1;
  namespace "urn:ietf:params:xml:ns:yang:ietf-nma-a2u-intent";
  prefix nma-a2u-intent;

  import ietf-nma-a2u-common { prefix nma-a2u-common; }
  import ietf-yang-types { prefix yang; }

  organization "IETF NMOP Working Group";
  contact
    "WG Web: https://datatracker.ietf.org/wg/nmop/
     WG List: nmop@ietf.org";
  description
    "YANG data model for NMA Intent (dual-modal: NL and Structured).

     Copyright (c) 2026 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     This version of this YANG module is part of RFC XXXX; see
     the RFC itself for full legal notices.";

  revision 2026-05-27 {
    description "Initial revision.";
    reference "RFC XXXX";
  }

  container intents {
    description "Container for all intents.";

    list intent {
      key "intent-id";
      description "A submitted intent.";

      leaf intent-id {
        type string;
        description "Unique intent identifier.";
      }

      leaf mode {
        type nma-a2u-common:intent-mode;
        mandatory true;
        description "Input mode: natural-language or structured.";
      }

      container submitter {
        uses nma-a2u-common:submitter-info;
        description "Who submitted this intent.";
      }

      leaf timestamp {
        type yang:date-and-time;
        mandatory true;
        description "Intent submission timestamp.";
      }

      leaf state {
        type nma-a2u-common:task-state;
        mandatory true;
        description "Current state of the intent.";
      }

      leaf task-id {
        type leafref {
          path "/ietf-nma-a2u-tasks:tasks/task/task-id";
        }
        description "Associated task identifier.";
      }

      choice mode-choice {
        description "Mode-specific content.";
        case natural-language {
          container natural-language {
            description "Natural language intent details.";

            leaf text {
              type string;
              mandatory true;
              description "Raw natural language input.";
            }

            leaf parsed-result {
              type anydata;
              description "Internal structured representation after parsing.";
            }

            leaf confidence {
              type decimal64 {
                fraction-digits 2;
                range "0..1";
              }
              description "Parsing confidence score.";
            }

            leaf parser {
              type enumeration {
                enum llm { description "LLM-based parser."; }
                enum rule { description "Rule-based parser."; }
                enum hybrid { description "Hybrid parser."; }
              }
              description "Parser type used.";
            }
          }
        }
        case structured {
          container structured {
            description "Structured intent details.";

            leaf type {
              type nma-a2u-common:intent-type;
              mandatory true;
              description "Type of operation.";
            }

            leaf target-resource {
              type string;
              description "Target resource identifier.";
            }

            leaf constraints {
              type anydata;
              mandatory true;
              description "Domain-specific constraints. External YANG modules may define the structure.";
            }

            leaf priority {
              type uint8 {
                range "1..10";
              }
              default "5";
              description "Priority level (1=lowest, 10=highest).";
            }
          }
        }
      }

      leaf estimated-completion {
        type uint32;
        units "seconds";
        config false;
        description "Estimated time to complete in seconds.";
      }
    }
  }
}
