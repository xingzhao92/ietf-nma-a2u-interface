module ietf-nma-a2u-capabilities {
  yang-version 1.1;
  namespace "urn:ietf:params:xml:ns:yang:ietf-nma-a2u-capabilities";
  prefix nma-a2u-cap;

  import ietf-nma-a2u-common { prefix nma-a2u-common; }
  import ietf-inet-types { prefix inet; }

  organization "IETF NMOP Working Group";
  contact
    "WG Web: https://datatracker.ietf.org/wg/nmop/
     WG List: nmop@ietf.org";
  description
    "YANG data model for NMA Agent Capability discovery (Agent Card).

     Copyright (c) 2026 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     This version of this YANG module is part of RFC XXXX; see
     the RFC itself for full legal notices.";

  revision 2026-05-27 {
    description "Initial revision.";
    reference "RFC XXXX";
  }

  container agent-capabilities {
    config false;
    description "Agent capability discovery information.";

    leaf agent-id {
      type string;
      mandatory true;
      description "Unique identifier of the NMA.";
    }

    leaf version {
      type string;
      mandatory true;
      description "Version of the NMA implementation.";
    }

    list skills {
      key "skill-id";
      description "Skills exposed by the NMA.";

      leaf skill-id {
        type string;
        description "Unique skill identifier.";
      }

      leaf name {
        type string;
        mandatory true;
        description "Human-readable skill name.";
      }

      leaf description {
        type string;
        description "Detailed description of the skill.";
      }

      leaf input-schema {
        type union {
          type inet:uri;
          type string;
        }
        description "URI referencing a YANG module, or inline schema description.";
      }

      leaf confirmation-required {
        type boolean;
        default "false";
        description "Whether this skill requires confirmation by default.";
      }

      leaf max-autonomy-level {
        type nma-a2u-common:autonomy-level;
        mandatory true;
        description "Maximum autonomy level this skill can operate at.";
      }

      leaf-list tags {
        type string;
        description "Categorization tags for the skill.";
      }
    }

    list endpoints {
      key "name";
      description "Available API endpoints.";

      leaf name {
        type string;
        description "Endpoint name.";
      }

      leaf uri {
        type inet:uri;
        mandatory true;
        description "Endpoint URI.";
      }

      leaf-list methods {
        type string;
        description "Supported HTTP methods.";
      }
    }

    container policies {
      description "Global policies of the NMA.";

      leaf default-autonomy-level {
        type nma-a2u-common:autonomy-level;
        description "Default autonomy level for all skills.";
      }

      leaf human-in-the-loop {
        type boolean;
        default "true";
        description "Whether human-in-the-loop is globally enabled.";
      }

      leaf max-timeout-seconds {
        type uint32;
        description "Maximum timeout for task execution in seconds.";
      }
    }
  }
}
