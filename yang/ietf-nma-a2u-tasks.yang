module ietf-nma-a2u-tasks {
  yang-version 1.1;
  namespace "urn:ietf:params:xml:ns:yang:ietf-nma-a2u-tasks";
  prefix nma-a2u-task;

  import ietf-nma-a2u-common { prefix nma-a2u-common; }
  import ietf-nma-a2u-intent { prefix nma-a2u-intent; }
  import ietf-yang-types { prefix yang; }

  organization "IETF NMOP Working Group";
  contact
    "WG Web: https://datatracker.ietf.org/wg/nmop/
     WG List: nmop@ietf.org";
  description
    "YANG data model for NMA Task lifecycle management.

     Copyright (c) 2026 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     This version of this YANG module is part of RFC XXXX; see
     the RFC itself for full legal notices.";

  revision 2026-05-27 {
    description "Initial revision.";
    reference "RFC XXXX";
  }

  container tasks {
    config false;
    description "Container for all tasks.";

    list task {
      key "task-id";
      description "A task instantiated from an intent.";

      leaf task-id {
        type string;
        description "Unique task identifier.";
      }

      leaf parent-intent-id {
        type leafref {
          path "/nma-a2u-intent:intents/nma-a2u-intent:intent/nma-a2u-intent:intent-id";
        }
        mandatory true;
        description "The intent that spawned this task.";
      }

      leaf state {
        type nma-a2u-common:task-state;
        mandatory true;
        description "Current task state.";
      }

      leaf created-at {
        type yang:date-and-time;
        mandatory true;
        description "Task creation timestamp.";
      }

      leaf updated-at {
        type yang:date-and-time;
        mandatory true;
        description "Last state update timestamp.";
      }

      list plan {
        key "step-id";
        description "Execution plan steps.";

        leaf step-id {
          type string;
          description "Unique step identifier.";
        }

        leaf action {
          type string;
          mandatory true;
          description "Action name or API call.";
        }

        leaf target {
          type string;
          description "Target resource or component.";
        }

        leaf input-params {
          type anydata;
          description "Input parameters for this step.";
        }

        leaf status {
          type enumeration {
            enum pending { description "Step pending execution."; }
            enum running { description "Step currently executing."; }
            enum completed { description "Step completed successfully."; }
            enum failed { description "Step failed."; }
            enum skipped { description "Step skipped."; }
          }
          mandatory true;
          description "Step execution status.";
        }

        leaf observation {
          type string;
          description "Observation or output from this step.";
        }

        leaf started-at {
          type yang:date-and-time;
          description "Step start timestamp.";
        }

        leaf completed-at {
          type yang:date-and-time;
          description "Step completion timestamp.";
        }
      }

      container result {
        description "Final task result.";

        leaf success {
          type boolean;
          mandatory true;
          description "Whether the task succeeded.";
        }

        leaf summary {
          type string;
          mandatory true;
          description "Human-readable summary of the result.";
        }

        leaf-list affected-resources {
          type string;
          description "List of resources affected by this task.";
        }

        leaf output-data {
          type anydata;
          description "Structured output data.";
        }
      }

      list audit-log {
        key "log-id";
        description "Audit trail for the task.";

        leaf log-id {
          type string;
          description "Unique log entry identifier.";
        }

        leaf timestamp {
          type yang:date-and-time;
          mandatory true;
          description "Log entry timestamp.";
        }

        leaf actor {
          type string;
          mandatory true;
          description "Who performed the action (user, system, or NMA).";
        }

        leaf action {
          type string;
          mandatory true;
          description "Action performed.";
        }

        leaf details {
          type string;
          description "Additional details.";
        }
      }
    }
  }
}
